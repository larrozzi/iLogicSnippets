oMyParameter = ThisApplication.ActiveDocument.ComponentDefinition.Parameters.UserParameters

Dim userParam As String = "DiaDrainHole"


For index As Integer = 1 To 10
	
''	Setting a userParameter as a number in inches
'	Dim paramVal As String = "3"
'	oParameter = oMyParameter.AddByExpression(userParam + index.ToString, paramVal, UnitsTypeEnum.kInchLengthUnits)
'	oParameter = oMyParameter.AddByExpression(userParamForm + index.ToString, paramVal, UnitsTypeEnum.kInchLengthUnits)
	
'	'Setting a UserParameter As MultiValue Text list
'	oParameter = oMyParameter.AddByValue(userParam + index.ToString, "1.25", UnitsTypeEnum.kTextUnits)
'	MultiValue.SetList(userParam + index.ToString, "1.25", "2.5", "n/a")
'	oParameter = oMyParameter.AddByValue(userParam + index.ToString + "Form", "1.25", UnitsTypeEnum.kTextUnits)
'	MultiValue.SetList(userParam + index.ToString + "Form", "1.25", "2.5", "n/a")
	
	'Setting a userParameter as multivalue number list
	oParameter = oMyParameter.AddByExpression(userParam + index.ToString, "1.25", UnitsTypeEnum.kInchLengthUnits)
	'MultiValue.SetList(userParam + index.ToString, "1.25", "2.5")

	oParameter = oMyParameter.AddByValue(userParam + index.ToString + "Form", 1.25, UnitsTypeEnum.kInchLengthUnits)
	MultiValue.SetList(userParam + index.ToString + "Form", 1.25, 2.5)

Next



'variables/values that would come from the model
Material = "Steel"
Thickness = 0.103587
Width = 1.5625
Length = 6.3987

'convert values to fraction
oT = RoundToFraction(Thickness, 1/8, RoundingMethod.RoundUp)
oW = RoundToFraction(Width, 1/16, RoundingMethod.RoundUp)
oL = RoundToFraction(Length, 1/32, RoundingMethod.RoundUp)

'set description
iProperties.Value("Project", "Description") = _
oT & " " & Material & " x " & oW & " in. x " & oL & " in. Lg."

'display to user
MessageBox.Show("Description: " & vbLf & _
iProperties.Value("Project", "Description"), "iLogic")
